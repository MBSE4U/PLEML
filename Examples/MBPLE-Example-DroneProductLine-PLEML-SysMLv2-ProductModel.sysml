// MIT License
//
// Copyright (c) 2026 Tim Weilkiens, Marco Forlingieri, Vince Molnar
//
// Permission is hereby granted, free of charge, to any person obtaining a copy
// of this software and associated documentation files (the "Software"), to deal
// in the Software without restriction, including without limitation the rights
// to use, copy, modify, merge, publish, distribute, sublicense, and/or sell
// copies of the Software, and to permit persons to whom the Software is
// furnished to do so, subject to the following conditions:
//
// The above copyright notice and this permission notice shall be included in all
// copies or substantial portions of the Software.
//
// THE SOFTWARE IS PROVIDED "AS IS", WITHOUT WARRANTY OF ANY KIND, EXPRESS OR
// IMPLIED, INCLUDING BUT NOT LIMITED TO THE WARRANTIES OF MERCHANTABILITY,
// FITNESS FOR A PARTICULAR PURPOSE AND NONINFRINGEMENT. IN NO EVENT SHALL THE
// AUTHORS OR COPYRIGHT HOLDERS BE LIABLE FOR ANY CLAIM, DAMAGES OR OTHER
// LIABILITY, WHETHER IN AN ACTION OF CONTRACT, TORT OR OTHERWISE, ARISING FROM,
// OUT OF OR IN CONNECTION WITH THE SOFTWARE OR THE USE OR OTHER DEALINGS IN THE
// SOFTWARE.

package <PRODUCT_DD> DeliveryDroneProductModel {
    @PLEML::FCFGB { featureConfiguration = "deliveryDrone"; }
    doc
    /* Product Model of a Delivery Drone (member product of the product line)
     *
     * Can be automatically generated by the following steps:
     * 1. Select feature configuration for the delivery drone member product.
     * 2. Create subclassifications or subsettings of the root shared assets if it contains feature bindings.
     * 3. For each feature binding of a shared asset:
     *      a) Shared asset is a variation: Bind the corresponding variant according to the feature configuration and nested feature bindings.
     *      b) Shared asset has multiplicity [0..1]: Set multiplicity to 0 or 1 according to the feature configuration.
     */

    private import DroneProductLineSharedAssets::*;

    package <DD_RE> DeliveryDroneSystemRequirements {
        requirement def DeliveryDroneSystemRequirementsSpecification
            :> DPL_RE::DroneSystemRequirementsSpecification {
            requirement :>> minimumFlightTime = minimumFlightTime::extendedRange;
        }
    } // package <DD_RE> DeliveryDroneSystemRequirements
    package <DD_SA> DeliveryDroneSystemArchitecture {
        part def DeliveryDrone :> DPL_SA::Drone {
            part :>> body = body::bodyWithLargePayload;
            action :>> controlUnit.charging = controlUnit.charging::longDistanceCharging;
            part :>> engines = engines::engines6;
            part :>> battery = battery::longDistanceBattery;
        }
    } // package <DD_SA> DeliveryDroneSystemArchitecture
} // package <PRODUCT_DD> DeliveryDroneProductModel
